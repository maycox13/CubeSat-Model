# CommsStandardRequirements

## #1: Uplink Frequencies (Functional)

### #2: S-band Frequencies (Functional)
The low rate antenna component "status" variable shall be set to "on" when a s-band signal between 2 and 4 gigahertz (GHz) is received by the communication subsystem.
